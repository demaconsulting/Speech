package SpeechOnnxKokoro {
    part def SpeechModelCatalogKokoroExtensions {
        doc /* Public AddKokoroModels() extension method that registers the one
             * ONNX-Runtime-backed Kokoro model with a SpeechModelCatalog and returns the same
             * catalog for chaining. Documented as a subsystem unit (no separate unit-level
             * companion files), mirroring SpeechSherpa's SpeechModelCatalogSherpaExtensions
             * convention. */

        comment sourceRef /* Source: src/DemaConsulting.Speech.Onnx.Kokoro/SpeechModelCatalogKokoroExtensions.cs */
        comment testRef /* Test: test/DemaConsulting.Speech.Onnx.Kokoro.Tests/SpeechModelCatalogKokoroExtensionsTests.cs */
        comment designRef /* Design: docs/design/speech-onnx-kokoro/model-management-subsystem.md (documented as a subsystem unit) */
        comment verificationRef /* Verification: docs/verification/speech-onnx-kokoro/model-management-subsystem.md (documented as a subsystem unit) */
        comment reqRef /* Requirements: docs/reqstream/speech-onnx-kokoro/model-management-subsystem.yaml (consolidated at subsystem level) */
    }
}
