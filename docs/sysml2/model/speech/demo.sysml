package Speech {
    part def Demo {
        doc /* Demonstration greeting class showing how a DEMA Consulting .NET library class should be structured, documented, and tested. */

        comment sourceRef /* Source: src/DemaConsulting.Speech/Demo.cs */
        comment testRef /* Test: test/DemaConsulting.Speech.Tests/DemoTests.cs */
        comment designRef /* Design: docs/design/speech/demo.md */
        comment verificationRef /* Verification: docs/verification/speech/demo.md */
        comment reqRef /* Requirements: docs/reqstream/speech/demo.yaml */
    }
}
