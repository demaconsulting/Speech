package Speech {
    part def IAudioPlaybackDeviceProbe {
        doc /* Contract for enumerating available audio playback devices, independent of any real
             * hardware or native runtime. */

        comment sourceRef /* Source: src/DemaConsulting.Speech/AudioSubsystem/IAudioPlaybackDeviceProbe.cs */
        comment designRef /* Design: docs/design/speech/audio-subsystem/i-audio-playback-device-probe.md */
        comment verificationRef /* Verification: docs/verification/speech/audio-subsystem/i-audio-playback-device-probe.md */
        comment reqRef /* Requirements: docs/reqstream/speech/audio-subsystem/i-audio-playback-device-probe.yaml */
    }
}
