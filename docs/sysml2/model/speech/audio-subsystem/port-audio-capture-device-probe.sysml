package Speech {
    part def PortAudioCaptureDeviceProbe {
        doc /* Preferred-host filtered capture-device probe backed by PortAudio device metadata
             * exposed through the internal PortAudio seam. */

        comment sourceRef /* Source: src/DemaConsulting.Speech/AudioSubsystem/PortAudioCaptureDeviceProbe.cs */
        comment testRef /* Test: test/DemaConsulting.Speech.Tests/AudioSubsystem/PortAudioCaptureDeviceProbeTests.cs */
        comment designRef /* Design: docs/design/speech/audio-subsystem/port-audio-capture-device-probe.md */
        comment verificationRef /* Verification: docs/verification/speech/audio-subsystem/port-audio-capture-device-probe.md */
        comment reqRef /* Requirements: docs/reqstream/speech/audio-subsystem/port-audio-capture-device-probe.yaml */
    }
}
