package Speech {
    part def AudioResampler {
        doc /* Down-mixes and windowed-sinc resamples floating-point audio. */

        comment sourceRef /* Source: src/DemaConsulting.Speech/AudioSubsystem/AudioResampler.cs */
        comment testRef /* Test: test/DemaConsulting.Speech.Tests/AudioSubsystem/AudioResamplerTests.cs */
        comment designRef /* Design: docs/design/speech/audio-subsystem/audio-resampler.md */
        comment verificationRef /* Verification: docs/verification/speech/audio-subsystem/audio-resampler.md */
        comment reqRef /* Requirements: docs/reqstream/speech/audio-subsystem/audio-resampler.yaml */
    }
}
