package Speech {
    part def AudioClip {
        doc /* Immutable decoded-audio value with derived frame count, duration, mono and PCM16 views. */

        comment sourceRef /* Source: src/DemaConsulting.Speech/AudioSubsystem/AudioClip.cs */
        comment testRef /* Test: test/DemaConsulting.Speech.Tests/AudioSubsystem/AudioFileReaderTests.cs */
        comment designRef /* Design: docs/design/speech/audio-subsystem/audio-clip.md */
        comment verificationRef /* Verification: docs/verification/speech/audio-subsystem/audio-clip.md */
        comment reqRef /* Requirements: docs/reqstream/speech/audio-subsystem/audio-clip.yaml */
    }
}
