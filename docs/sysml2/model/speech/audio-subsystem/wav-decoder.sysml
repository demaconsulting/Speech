package Speech {
    part def WavDecoder {
        doc /* Internal RIFF/WAVE decoder for PCM 8/16/24/32-bit and float32 audio. */

        comment sourceRef /* Source: src/DemaConsulting.Speech/AudioSubsystem/WavDecoder.cs */
        comment testRef /* Test: test/DemaConsulting.Speech.Tests/AudioSubsystem/WavDecoderTests.cs */
        comment designRef /* Design: docs/design/speech/audio-subsystem/wav-decoder.md */
        comment verificationRef /* Verification: docs/verification/speech/audio-subsystem/wav-decoder.md */
        comment reqRef /* Requirements: docs/reqstream/speech/audio-subsystem/wav-decoder.yaml */
    }
}
