package Speech {
    part def FlacDecoder {
        doc /* Internal managed FLAC decoder (stream, frame, bit reader and CRC helpers) for AudioFileReader. */

        comment sourceRef /* Source: src/DemaConsulting.Speech/AudioSubsystem/FlacDecoder.cs, src/DemaConsulting.Speech/AudioSubsystem/FlacFrameDecoder.cs, src/DemaConsulting.Speech/AudioSubsystem/FlacBitReader.cs, src/DemaConsulting.Speech/AudioSubsystem/FlacCrc.cs */
        comment testRef /* Test: test/DemaConsulting.Speech.Tests/AudioSubsystem/FlacDecoderTests.cs */
        comment designRef /* Design: docs/design/speech/audio-subsystem/flac-decoder.md */
        comment verificationRef /* Verification: docs/verification/speech/audio-subsystem/flac-decoder.md */
        comment reqRef /* Requirements: docs/reqstream/speech/audio-subsystem/flac-decoder.yaml */
    }
}
