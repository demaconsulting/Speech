package Speech {
    part def IAudioCaptureDeviceProbe {
        doc /* Contract for enumerating available audio capture devices, independent of any real
             * hardware or native runtime. */

        comment sourceRef /* Source: src/DemaConsulting.Speech/AudioSubsystem/IAudioCaptureDeviceProbe.cs */
        comment designRef /* Design: docs/design/speech/audio-subsystem/i-audio-capture-device-probe.md */
        comment verificationRef /* Verification: docs/verification/speech/audio-subsystem/i-audio-capture-device-probe.md */
        comment reqRef /* Requirements: docs/reqstream/speech/audio-subsystem/i-audio-capture-device-probe.yaml */
    }
}
