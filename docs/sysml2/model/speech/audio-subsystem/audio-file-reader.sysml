package Speech {
    part def AudioFileReader {
        doc /* Decodes WAV and FLAC files or streams into AudioClip values with managed code only. */

        comment sourceRef /* Source: src/DemaConsulting.Speech/AudioSubsystem/AudioFileReader.cs, src/DemaConsulting.Speech/AudioSubsystem/AudioFileReadOptions.cs */
        comment testRef /* Test: test/DemaConsulting.Speech.Tests/AudioSubsystem/AudioFileReaderTests.cs */
        comment designRef /* Design: docs/design/speech/audio-subsystem/audio-file-reader.md */
        comment verificationRef /* Verification: docs/verification/speech/audio-subsystem/audio-file-reader.md */
        comment reqRef /* Requirements: docs/reqstream/speech/audio-subsystem/audio-file-reader.yaml */
    }
}
