package Speech {
    part def AudioDeviceDescription {
        doc /* Immutable record describing one audio device by name (its sole identity key),
             * direction, channel count, and sample rate. */

        comment sourceRef /* Source: src/DemaConsulting.Speech/AudioSubsystem/AudioDeviceDescription.cs */
        comment designRef /* Design: docs/design/speech/audio-subsystem/audio-device-description.md */
        comment verificationRef /* Verification: docs/verification/speech/audio-subsystem/audio-device-description.md */
        comment reqRef /* Requirements: docs/reqstream/speech/audio-subsystem/audio-device-description.yaml */
    }
}
