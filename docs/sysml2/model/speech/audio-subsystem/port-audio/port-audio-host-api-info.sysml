package Speech {
    part def PortAudioHostApiInfo {
        doc /* Managed metadata record describing one PortAudio host API, including its stable type
             * identifier and default input/output device indices. */

        comment sourceRef /* Source: src/DemaConsulting.Speech/AudioSubsystem/PortAudio/PortAudioHostApiInfo.cs */
        comment designRef /* Design: docs/design/speech/audio-subsystem/port-audio/port-audio-supporting-types.md */
        comment verificationRef /* Verification: docs/verification/speech/audio-subsystem/port-audio/port-audio-supporting-types.md */
        comment reqRef /* Requirements: docs/reqstream/speech/audio-subsystem/port-audio/port-audio-supporting-types.yaml */
    }
}
