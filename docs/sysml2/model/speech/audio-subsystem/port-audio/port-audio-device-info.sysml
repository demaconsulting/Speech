package Speech {
    part def PortAudioDeviceInfo {
        doc /* Managed metadata record describing one PortAudio device without exposing native
             * binding structs to higher-level logic. */

        comment sourceRef /* Source: src/DemaConsulting.Speech/AudioSubsystem/PortAudio/PortAudioDeviceInfo.cs */
        comment designRef /* Design: docs/design/speech/audio-subsystem/port-audio/port-audio-supporting-types.md */
        comment verificationRef /* Verification: docs/verification/speech/audio-subsystem/port-audio/port-audio-supporting-types.md */
        comment reqRef /* Requirements: docs/reqstream/speech/audio-subsystem/port-audio/port-audio-supporting-types.yaml */
    }
}
