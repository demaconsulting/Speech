package Speech {
    part def PortAudioHostApiType {
        doc /* Internal enum carrying the stable PortAudio host-API constants used by platform
             * policy before runtime host-API indices are resolved. */

        comment sourceRef /* Source: src/DemaConsulting.Speech/AudioSubsystem/PortAudio/PortAudioHostApiType.cs */
        comment designRef /* Design: docs/design/speech/audio-subsystem/port-audio/port-audio-supporting-types.md */
        comment verificationRef /* Verification: docs/verification/speech/audio-subsystem/port-audio/port-audio-supporting-types.md */
        comment reqRef /* Requirements: docs/reqstream/speech/audio-subsystem/port-audio/port-audio-supporting-types.yaml */
    }
}
