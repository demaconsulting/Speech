package Speech {
    part def PortAudioNativeMethods {
        doc /* Repository-local P/Invoke declarations for PortAudio host-API functions absent from
             * PortAudioSharp2. */

        comment sourceRef /* Source: src/DemaConsulting.Speech/AudioSubsystem/PortAudio/PortAudioNativeMethods.cs */
        comment designRef /* Design: docs/design/speech/audio-subsystem/port-audio/port-audio-supporting-types.md */
        comment verificationRef /* Verification: docs/verification/speech/audio-subsystem/port-audio/port-audio-supporting-types.md */
        comment reqRef /* Requirements: docs/reqstream/speech/audio-subsystem/port-audio/port-audio-supporting-types.yaml */
    }
}
