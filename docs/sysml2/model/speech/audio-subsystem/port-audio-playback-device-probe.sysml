package Speech {
    part def PortAudioPlaybackDeviceProbe {
        doc /* Preferred-host filtered playback-device probe backed by PortAudio device metadata
             * exposed through the internal PortAudio seam. */

        comment sourceRef /* Source: src/DemaConsulting.Speech/AudioSubsystem/PortAudioPlaybackDeviceProbe.cs */
        comment testRef /* Test: test/DemaConsulting.Speech.Tests/AudioSubsystem/PortAudioPlaybackDeviceProbeTests.cs */
        comment designRef /* Design: docs/design/speech/audio-subsystem/port-audio-playback-device-probe.md */
        comment verificationRef /* Verification: docs/verification/speech/audio-subsystem/port-audio-playback-device-probe.md */
        comment reqRef /* Requirements: docs/reqstream/speech/audio-subsystem/port-audio-playback-device-probe.yaml */
    }
}
