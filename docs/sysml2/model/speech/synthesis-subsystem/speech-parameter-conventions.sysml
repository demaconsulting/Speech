package Speech {
    part def SpeechParameterConventions {
        doc /* Supporting constants holding the conservative, built-in naming conventions that
             * DefaultModelCapabilityProfile and SynthesisSession use to recognize which of a model's own
             * numeric parameters conventionally controls speaking rate or output volume. */

        comment sourceRef /* Source: src/DemaConsulting.Speech/SynthesisSubsystem/SpeechParameterConventions.cs */
        comment testRef /* Test: test/DemaConsulting.Speech.Tests/SynthesisSubsystem/SynthesisSessionTests.cs */
        comment designRef /* Design: docs/design/speech/synthesis-subsystem.md (documented as a supporting type) */
                comment verificationRef /* Verification: docs/verification/speech/synthesis-subsystem.md (verified within the subsystem doc; no dedicated unit doc) */
                comment reqRef /* Requirements: docs/reqstream/speech/synthesis-subsystem.yaml (requirements held in the subsystem file; no dedicated unit file) */    }
}
