package Speech {
    part def SpeechDiagnosticLevel {
        doc /* Supporting enumeration identifying the severity (informational, warning or error) of a
             * structural fact reported through ISpeechDiagnostics. */

        comment sourceRef /* Source: src/DemaConsulting.Speech/Diagnostics/SpeechDiagnosticLevel.cs */
        comment testRef /* Test: test/DemaConsulting.Speech.Tests/Diagnostics/NullSpeechDiagnosticsTests.cs */
        comment designRef /* Design: docs/design/speech/diagnostics.md (documented as a supporting type) */
                comment verificationRef /* Verification: docs/verification/speech/diagnostics.md (verified within the subsystem doc; no dedicated unit doc) */
                comment reqRef /* Requirements: docs/reqstream/speech/diagnostics.yaml (requirements held in the subsystem file; no dedicated unit file) */    }
}
