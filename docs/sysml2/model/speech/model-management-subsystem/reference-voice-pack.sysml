package Speech {
    part def ReferenceVoicePack {
        doc /* Descriptor of a downloadable reference-voice pack (archive URL, size, SHA-256,
             * license, attribution, measured installed sizes of voices and emotion clips), the built-in
             * voice-zero 1.0 pack, and the ReferenceVoiceInfo (including MoodClips) and
             * ReferenceVoiceSource value types that describe a listed voice. */

        comment sourceRef /* Source: src/DemaConsulting.Speech/ModelManagementSubsystem/ReferenceVoicePack.cs, ReferenceVoiceInfo.cs, ReferenceVoiceSource.cs */
        comment testRef /* Test: test/DemaConsulting.Speech.Tests/ModelManagementSubsystem/ReferenceVoicePackTests.cs */
        comment designRef /* Design: docs/design/speech/model-management-subsystem/reference-voice-pack.md */
        comment verificationRef /* Verification: docs/verification/speech/model-management-subsystem/reference-voice-pack.md */
        comment reqRef /* Requirements: docs/reqstream/speech/model-management-subsystem/reference-voice-pack.yaml */
    }
}
