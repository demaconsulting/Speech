package Speech {
    part def SpeechModelDownloadDescriptor {
        doc /* Describes the full set of files required to install a model: an ordered,
             * non-empty list of SpeechModelDownloadFile entries with unique relative install
             * paths. */

        comment sourceRef /* Source: src/DemaConsulting.Speech/ModelManagementSubsystem/SpeechModelDownloadDescriptor.cs */
        comment testRef /* Test: test/DemaConsulting.Speech.Tests/ModelManagementSubsystem/SpeechModelDownloadDescriptorTests.cs */
        comment designRef /* Design: docs/design/speech/model-management-subsystem/speech-model-download-descriptor.md */
        comment verificationRef /* Verification: docs/verification/speech/model-management-subsystem/speech-model-download-descriptor.md */
        comment reqRef /* Requirements: docs/reqstream/speech/model-management-subsystem/speech-model-download-descriptor.yaml */
    }
}
