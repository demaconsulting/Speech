package Speech {
    part def SpeechModelDownloadFile {
        doc /* Describes one downloadable file within a model: its HTTPS source URI, expected
             * SHA-256 checksum, and relative install path beneath the model's install root. */

        comment sourceRef /* Source: src/DemaConsulting.Speech/ModelManagementSubsystem/SpeechModelDownloadFile.cs */
        comment testRef /* Test: test/DemaConsulting.Speech.Tests/ModelManagementSubsystem/SpeechModelDownloadFileTests.cs */
        comment designRef /* Design: docs/design/speech/model-management-subsystem/speech-model-download-file.md */
        comment verificationRef /* Verification: docs/verification/speech/model-management-subsystem/speech-model-download-file.md */
        comment reqRef /* Requirements: docs/reqstream/speech/model-management-subsystem/speech-model-download-file.yaml */
    }
}
