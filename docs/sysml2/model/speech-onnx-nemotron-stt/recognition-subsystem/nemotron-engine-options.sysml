package SpeechOnnxNemotronStt {
    part def NemotronEngineOptions {
        doc /* Supporting record holding the tunable constants of OnnxNemotronRecognitionEngine; the
             * defaults are the documented production values and tests supply others for edge cases. */

        comment sourceRef /* Source: src/DemaConsulting.Speech.Onnx.NemotronStt/RecognitionSubsystem/NemotronEngineOptions.cs */
        comment testRef /* Test: test/DemaConsulting.Speech.Onnx.NemotronStt.Tests/RecognitionSubsystem/OnnxNemotronRecognitionEngineTests.cs */
        comment designRef /* Design: docs/design/speech-onnx-nemotron-stt/recognition-subsystem/onnx-nemotron-recognition-engine.md (documented as a supporting type) */
                comment verificationRef /* Verification: docs/verification/speech-onnx-nemotron-stt/recognition-subsystem/onnx-nemotron-recognition-engine.md (verified within the engine unit doc; no dedicated doc) */
                comment reqRef /* Requirements: docs/reqstream/speech-onnx-nemotron-stt/recognition-subsystem/onnx-nemotron-recognition-engine.yaml (requirements held in the engine unit file; no dedicated file) */    }
}
