package SpeechOnnxChatterboxTurbo {
    part def ChatterboxTurboReferenceVoice {
        doc /* A reference voice created from in-memory audio or a WAV or FLAC file,
             * normalized to mono 24 kHz (via the core AudioResampler) and bounded in length. */

        comment sourceRef /* Source: src/DemaConsulting.Speech.Onnx.ChatterboxTurbo/ModelManagementSubsystem/ChatterboxTurboReferenceVoice.cs */
        comment testRef /* Test: test/DemaConsulting.Speech.Onnx.ChatterboxTurbo.Tests/ModelManagementSubsystem/ChatterboxTurboReferenceVoiceTests.cs */
        comment designRef /* Design: docs/design/speech-onnx-chatterboxturbo/model-management-subsystem/chatterbox-turbo-reference-voice.md */
        comment verificationRef /* Verification: docs/verification/speech-onnx-chatterboxturbo/model-management-subsystem/chatterbox-turbo-reference-voice.md */
        comment reqRef /* Requirements: docs/reqstream/speech-onnx-chatterboxturbo/model-management-subsystem/chatterbox-turbo-reference-voice.yaml */
    }
}
