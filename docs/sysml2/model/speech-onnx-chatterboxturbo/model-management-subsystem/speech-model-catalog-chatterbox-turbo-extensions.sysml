package SpeechOnnxChatterboxTurbo {
    part def SpeechModelCatalogChatterboxTurboExtensions {
        doc /* Public AddChatterboxTurboModels() extension method that registers the one
             * ONNX-Runtime-backed Chatterbox Turbo model with a SpeechModelCatalog and returns
             * the same catalog for chaining. */

        comment sourceRef /* Source: src/DemaConsulting.Speech.Onnx.ChatterboxTurbo/SpeechModelCatalogChatterboxTurboExtensions.cs */
        comment testRef /* Test: test/DemaConsulting.Speech.Onnx.ChatterboxTurbo.Tests/ModelManagementSubsystem/SpeechModelCatalogChatterboxTurboExtensionsTests.cs */
        comment designRef /* Design: docs/design/speech-onnx-chatterboxturbo/model-management-subsystem/speech-model-catalog-chatterbox-turbo-extensions.md */
        comment verificationRef /* Verification: docs/verification/speech-onnx-chatterboxturbo/model-management-subsystem/speech-model-catalog-chatterbox-turbo-extensions.md */
        comment reqRef /* Requirements: docs/reqstream/speech-onnx-chatterboxturbo/model-management-subsystem/speech-model-catalog-chatterbox-turbo-extensions.yaml */
    }
}
