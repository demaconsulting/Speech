package SpeechOnnxChatterboxTurbo {
    part def OnnxChatterboxTurboNetworks {
        doc /* The raw ONNX Runtime sessions for the speech encoder, token embedder, language
             * model and conditional decoder, with thread configuration and deterministic
             * disposal. */

        comment sourceRef /* Source: src/DemaConsulting.Speech.Onnx.ChatterboxTurbo/SynthesisSubsystem/OnnxChatterboxTurboNetworks.cs, src/DemaConsulting.Speech.Onnx.ChatterboxTurbo/SynthesisSubsystem/IChatterboxTurboNetworks.cs, src/DemaConsulting.Speech.Onnx.ChatterboxTurbo/SynthesisSubsystem/IChatterboxTurboLanguageModelState.cs */
        comment testRef /* Test: test/DemaConsulting.Speech.Onnx.ChatterboxTurbo.Tests/SynthesisSubsystem/OnnxChatterboxTurboNetworksTests.cs */
        comment designRef /* Design: docs/design/speech-onnx-chatterboxturbo/synthesis-subsystem/onnx-chatterboxturbo-networks.md */
        comment verificationRef /* Verification: docs/verification/speech-onnx-chatterboxturbo/synthesis-subsystem/onnx-chatterboxturbo-networks.md */
        comment reqRef /* Requirements: docs/reqstream/speech-onnx-chatterboxturbo/synthesis-subsystem/onnx-chatterboxturbo-networks.yaml */
    }
}
