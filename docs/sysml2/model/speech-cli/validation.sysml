package SpeechCli {
    part def Validation {
        doc /* Supporting internal static class that runs the CLI's built-in self-validation
             * checks and writes the results as TRX or JUnit XML. */

        comment sourceRef /* Source: src/DemaConsulting.Speech.Cli/SelfTest/Validation.cs */
        comment testRef /* Test: test/DemaConsulting.Speech.Cli.Tests/ProgramTests.cs, test/DemaConsulting.Speech.Cli.Tests/IntegrationTests.cs */
                comment designRef /* Design: docs/design/speech-cli/validation.md */
                comment verificationRef /* Verification: docs/verification/speech-cli/validation.md */
                comment reqRef /* Requirements: docs/reqstream/speech-cli/validation.yaml */
            }
}
