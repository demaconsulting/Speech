package SpeechCli {
    part def PathHelpers {
        doc /* Supporting internal helper providing safe path operations for the CLI commands. */

        comment sourceRef /* Source: src/DemaConsulting.Speech.Cli/Utilities/PathHelpers.cs */
        comment testRef /* Test: test/DemaConsulting.Speech.Cli.Tests/Utilities/PathHelpersTests.cs */
        comment designRef /* Design: docs/design/speech-cli/path-helpers.md */
        comment verificationRef /* Verification: docs/verification/speech-cli/path-helpers.md */
        comment reqRef /* Requirements: docs/reqstream/speech-cli/path-helpers.yaml */
    }
}
