package SpeechSherpa {
    part def SpeechModelCatalogSherpaExtensions {
        doc /* Public AddSherpaModels() extension method that registers the four sherpa-onnx
             * models with a SpeechModelCatalog and returns the same catalog for chaining. */

        comment sourceRef /* Source: src/DemaConsulting.Speech.Sherpa/SpeechModelCatalogSherpaExtensions.cs */
        comment testRef /* Test: test/DemaConsulting.Speech.Sherpa.Tests/ModelManagementSubsystem/SpeechModelCatalogSherpaExtensionsTests.cs */
        comment designRef /* Design: docs/design/speech-sherpa/model-management-subsystem.md (documented as a subsystem unit) */
        comment verificationRef /* Verification: docs/verification/speech-sherpa/model-management-subsystem.md (documented as a subsystem unit) */
        comment reqRef /* Requirements: docs/reqstream/speech-sherpa/model-management-subsystem.yaml (consolidated at subsystem level) */
    }
}
