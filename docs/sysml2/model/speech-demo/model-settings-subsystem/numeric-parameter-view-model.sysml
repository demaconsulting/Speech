package SpeechDemo {
    part def NumericParameterViewModel {
        doc /* Presentation state for one numeric parameter, starting at its declared default
             * and clamping every written value to its declared range. */

        comment sourceRef /* Source: src/DemaConsulting.Speech.Demo/ModelSettingsSubsystem/NumericParameterViewModel.cs */
        comment testRef /* Test: test/DemaConsulting.Speech.Demo.Tests/ModelSettingsSubsystem/ParameterViewModelsTests.cs */
        comment designRef /* Design: docs/design/speech-demo/model-settings-subsystem/parameter-view-models.md */
        comment verificationRef /* Verification: docs/verification/speech-demo/model-settings-subsystem/parameter-view-models.md */
        comment reqRef /* Requirements: docs/reqstream/speech-demo/model-settings-subsystem/parameter-view-models.yaml */
    }
}
