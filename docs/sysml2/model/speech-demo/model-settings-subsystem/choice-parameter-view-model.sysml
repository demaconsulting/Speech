package SpeechDemo {
    part def ChoiceParameterViewModel {
        doc /* Presentation state for one choice parameter, listing its declared options and
             * preselecting the option matching its declared default. */

        comment sourceRef /* Source: src/DemaConsulting.Speech.Demo/ModelSettingsSubsystem/ChoiceParameterViewModel.cs */
        comment testRef /* Test: test/DemaConsulting.Speech.Demo.Tests/ModelSettingsSubsystem/ParameterViewModelsTests.cs */
        comment designRef /* Design: docs/design/speech-demo/model-settings-subsystem/parameter-view-models.md */
        comment verificationRef /* Verification: docs/verification/speech-demo/model-settings-subsystem/parameter-view-models.md */
        comment reqRef /* Requirements: docs/reqstream/speech-demo/model-settings-subsystem/parameter-view-models.yaml */
    }
}
