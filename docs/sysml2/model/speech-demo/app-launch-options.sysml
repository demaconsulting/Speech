package SpeechDemo {
    part def AppLaunchOptions {
        doc /* The parser and holder of the demo's launch-time command-line options. */

        comment sourceRef /* Source: src/DemaConsulting.Speech.Demo/AppLaunchOptions.cs */
        comment testRef /* Test: test/DemaConsulting.Speech.Demo.Tests/AppLaunchOptionsTests.cs */
        comment designRef /* Design: docs/design/speech-demo/app-launch-options.md */
        comment verificationRef /* Verification: docs/verification/speech-demo/app-launch-options.md */
        comment reqRef /* Requirements: docs/reqstream/speech-demo/app-launch-options.yaml */
    }
}
