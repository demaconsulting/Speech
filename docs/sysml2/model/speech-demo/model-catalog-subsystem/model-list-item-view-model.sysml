package SpeechDemo {
    part def ModelListItemViewModel {
        doc /* One catalog row: a model's identity and role, its install state, its download
             * progress, and its failure explanation, plus the derived captions and
             * enablement values the row displays. */

        comment sourceRef /* Source: src/DemaConsulting.Speech.Demo/ModelCatalogSubsystem/ModelListItemViewModel.cs */
        comment testRef /* Test: test/DemaConsulting.Speech.Demo.Tests/ModelCatalogSubsystem/ModelListItemViewModelTests.cs */
        comment designRef /* Design: docs/design/speech-demo/model-catalog-subsystem/model-list-item-view-model.md */
        comment verificationRef /* Verification: docs/verification/speech-demo/model-catalog-subsystem/model-list-item-view-model.md */
        comment reqRef /* Requirements: docs/reqstream/speech-demo/model-catalog-subsystem/model-list-item-view-model.yaml */
    }
}
