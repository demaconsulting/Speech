package SpeechDemo {
    part def ReferenceVoicePackListItemViewModel {
        doc /* One reference voice pack row: the pack identity, size, license and attribution,
             * its install state, progress and failure explanation, the include-emotions option and
             * installed-size caption, plus the derived captions and enablement values the row
             * displays. */

        comment sourceRef /* Source: src/DemaConsulting.Speech.Demo/ModelCatalogSubsystem/ReferenceVoicePackListItemViewModel.cs */
        comment testRef /* Test: test/DemaConsulting.Speech.Demo.Tests/ModelCatalogSubsystem/ReferenceVoicePackListItemViewModelTests.cs */
        comment designRef /* Design: docs/design/speech-demo/model-catalog-subsystem/reference-voice-pack-list-item-view-model.md */
        comment verificationRef /* Verification: docs/verification/speech-demo/model-catalog-subsystem/reference-voice-pack-list-item-view-model.md */
        comment reqRef /* Requirements: docs/reqstream/speech-demo/model-catalog-subsystem/reference-voice-pack-list-item-view-model.yaml */
    }
}
