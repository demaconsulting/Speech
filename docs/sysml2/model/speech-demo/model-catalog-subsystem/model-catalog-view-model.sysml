package SpeechDemo {
    part def ModelCatalogViewModel {
        doc /* Presentation state for the catalog panel: the model rows, the selected row, the
             * refresh and download commands, the mirror-settings fields and apply command, and
             * the explanatory empty-catalog message, and the reference voice pack rows with their
             * install and remove commands. */

        comment sourceRef /* Source: src/DemaConsulting.Speech.Demo/ModelCatalogSubsystem/ModelCatalogViewModel.cs */
        comment testRef /* Test: test/DemaConsulting.Speech.Demo.Tests/ModelCatalogSubsystem/ModelCatalogViewModelTests.cs */
        comment designRef /* Design: docs/design/speech-demo/model-catalog-subsystem/model-catalog-view-model.md */
        comment verificationRef /* Verification: docs/verification/speech-demo/model-catalog-subsystem/model-catalog-view-model.md */
        comment reqRef /* Requirements: docs/reqstream/speech-demo/model-catalog-subsystem/model-catalog-view-model.yaml */
    }
}
