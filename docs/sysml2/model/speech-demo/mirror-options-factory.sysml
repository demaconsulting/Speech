package SpeechDemo {
    part def MirrorOptionsFactory {
        doc /* The shared validator that builds a download mirror from raw strings for both
             * launch-time and in-app mirror configuration. */

        comment sourceRef /* Source: src/DemaConsulting.Speech.Demo/MirrorOptionsFactory.cs */
        comment testRef /* Test: test/DemaConsulting.Speech.Demo.Tests/AppLaunchOptionsTests.cs (verified through its callers) */
        comment designRef /* Design: docs/design/speech-demo/mirror-options-factory.md */
        comment verificationRef /* Verification: docs/verification/speech-demo/mirror-options-factory.md */
        comment reqRef /* Requirements: docs/reqstream/speech-demo/mirror-options-factory.yaml */
    }
}
