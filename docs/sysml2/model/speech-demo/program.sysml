package SpeechDemo {
    part def Program {
        doc /* The process entry point: fails fast on invalid launch options and configures
             * the Avalonia application builder. */

        comment sourceRef /* Source: src/DemaConsulting.Speech.Demo/Program.cs */
        comment testRef /* Test: test/DemaConsulting.Speech.Demo.Tests/Ots/AvaloniaTests.cs */
        comment designRef /* Design: docs/design/speech-demo/program.md */
        comment verificationRef /* Verification: docs/verification/speech-demo/program.md */
        comment reqRef /* Requirements: docs/reqstream/speech-demo/program.yaml */
    }
}
