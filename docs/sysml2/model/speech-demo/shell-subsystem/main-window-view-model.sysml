package SpeechDemo {
    part def MainWindowViewModel {
        doc /* Navigation state for the application window: the ordered panel list and the
             * currently selected panel. */

        comment sourceRef /* Source: src/DemaConsulting.Speech.Demo/ShellSubsystem/MainWindowViewModel.cs */
        comment testRef /* Test: test/DemaConsulting.Speech.Demo.Tests/ShellSubsystem/MainWindowViewModelTests.cs */
        comment designRef /* Design: docs/design/speech-demo/shell-subsystem/main-window-view-model.md */
        comment verificationRef /* Verification: docs/verification/speech-demo/shell-subsystem/main-window-view-model.md */
        comment reqRef /* Requirements: docs/reqstream/speech-demo/shell-subsystem/main-window-view-model.yaml */
    }
}
