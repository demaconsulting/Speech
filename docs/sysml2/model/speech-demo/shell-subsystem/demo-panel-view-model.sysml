package SpeechDemo {
    part def DemoPanelViewModel {
        doc /* One navigable panel entry: a display title paired with the panel view model
             * the shell was composed with. */

        comment sourceRef /* Source: src/DemaConsulting.Speech.Demo/ShellSubsystem/DemoPanelViewModel.cs */
        comment testRef /* Test: test/DemaConsulting.Speech.Demo.Tests/ShellSubsystem/DemoPanelViewModelTests.cs */
        comment designRef /* Design: docs/design/speech-demo/shell-subsystem/demo-panel-view-model.md */
        comment verificationRef /* Verification: docs/verification/speech-demo/shell-subsystem/demo-panel-view-model.md */
        comment reqRef /* Requirements: docs/reqstream/speech-demo/shell-subsystem/demo-panel-view-model.yaml */
    }
}
