package SpeechDemo {
    part def App {
        doc /* The Avalonia application object and the demo's manual composition root: builds
             * the library entry points and demo service adapters and wires them into the
             * shell. */

        comment sourceRef /* Source: src/DemaConsulting.Speech.Demo/App.axaml.cs */
        comment testRef /* Test: test/DemaConsulting.Speech.Demo.Tests/SpeechDemoTests.cs */
        comment designRef /* Design: docs/design/speech-demo/app.md */
        comment verificationRef /* Verification: docs/verification/speech-demo/app.md */
        comment reqRef /* Requirements: docs/reqstream/speech-demo/app.yaml */
    }
}
